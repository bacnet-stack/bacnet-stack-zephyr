[DOCUMENT]
TITLE: BACnet Stack Stakeholders
REQ_PREFIX: BKSTK-STRS-STAKEHOLDERS

[GRAMMAR]
IMPORT_FROM_FILE: bacnet_stakeholder_needs.sgra

[TEXT]
STATEMENT: >>>
SPDX-LICENSE-IDENTIFIER: Apache-2.0
<<<

[SECTION]
TITLE: User Personas

[/SECTION]
