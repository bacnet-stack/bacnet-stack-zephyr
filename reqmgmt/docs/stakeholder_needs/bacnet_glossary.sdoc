[DOCUMENT]
TITLE: BACnet Stack Glossary
REQ_PREFIX: BKSTK-STRS-GLOSSARY

[GRAMMAR]
IMPORT_FROM_FILE: bacnet_stakeholder_needs.sgra

[TEXT]
STATEMENT: >>>
SPDX-LICENSE-IDENTIFIER: Apache-2.0
<<<

[TEXT]
STATEMENT: >>>
TBD
<<<
