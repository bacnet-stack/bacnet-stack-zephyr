[DOCUMENT]
TITLE: BACnet Stack Stakeholder Needs/Requirements Specification
REQ_PREFIX: BKSTK-STRS

[GRAMMAR]
IMPORT_FROM_FILE: bacnet_stakeholder_needs.sgra

[TEXT]
STATEMENT: >>>
SPDX-LICENSE-IDENTIFIER: Apache-2.0
<<<

[TEXT]
STATEMENT: >>>
BACnet open source protocol stack C library for
embedded systems, Linux, MacOS, BSD, and Windows
<<<

[TEXT]
STATEMENT: >>>
http://bacnet.sourceforge.net/
<<<

[SECTION]
TITLE: Project Information

[TEXT]
STATEMENT: >>>
This BACnet library provides a BACnet application layer,
network layer and media access (MAC) layer communications services
for an embedded system.
<<<

[TEXT]
STATEMENT: >>>
BACnet - A Data Communication Protocol for
Building Automation and Control Networks - see bacnet.org.
BACnet is a standard data communication protocol
for Building Automation and Control Networks.
BACnet is an open protocol, which means anyone can contribute to the standard,
and anyone may use it.  The only caveat is that the
BACnet standard document itself is copyrighted by ASHRAE, and they sell
the document to help defray costs of developing and maintaining the standard
(just like IEEE or ANSI or ISO).

For software developers, the BACnet protocol is a standard way to send and
receive messages containing data that are understood by other BACnet compliant
devices. The BACnet standard defines a standard way to communicate over
various wires or radios, known as Data Link/Physical Layers: Ethernet,
EIA-485, EIA-232, ARCNET, and LonTalk.
The BACnet standard also defines a standard way to communicate
using UDP, IP, HTTP (Web Services), and Websockets.
<<<

[TEXT]
STATEMENT: >>>
This BACnet protocol stack implementation is specifically designed for
the embedded BACnet appliance, using a GPL with exception license
(like eCos), which means that any changes to the core code that are
distributed are shared, but the BACnet library can be linked to
proprietary code without the proprietary code becoming GPL.
Note that some of the source files are designed as skeleton or
example or template files, and are not copyrighted as GPL.
<<<

[TEXT]
STATEMENT: >>>
The text of the GPL exception included in each source file is as follows:

- SPDX-License-Identifier: GPL-2.0-or-later WITH GCC-exception-2.0 ^^^^^^^^^^^^^^^^^^^^^^
<<<

[TEXT]
STATEMENT: >>>
The code is written in C for portability, and includes unit tests
(PC based unit tests). Since the code is designed to be portable,
it compiles with GCC as well as other compilers, such as Clang or IAR.
<<<

[TEXT]
STATEMENT: >>>
The BACnet protocol is an ASHRAE/ANSI/ISO standard, so this library adheres
to that standard. BACnet has no royalties or licensing restrictions, and
registration for a BACnet vendor ID is free.
<<<

[/SECTION]

[DOCUMENT_FROM_FILE]
FILE: bacnet_glossary.sdoc

[DOCUMENT_FROM_FILE]
FILE: bacnet_stakeholders.sdoc

[DOCUMENT_FROM_FILE]
FILE: bacnet_stakeholder_needs.sdoc

[DOCUMENT_FROM_FILE]
FILE: bacnet_stakeholder_constraints.sdoc

[DOCUMENT_FROM_FILE]
FILE: bacnet_stakeholder_con-ops.sdoc
